# Exported Reqif

# Specification: Sample Export Requirements
- IE PUID: SPEC-555422
- ReqIF.ForeignRevision: V1.1.2
- ReqIF.Name: Sample Export Requirements

## Chapter-2101: 1 (Folder)
Document Introduction
- IE Object Type: Function

### Requirement-555555: 1.1 (Requirement)
First Requirement
Test String
- IE Object Type: Requirement

## Chapter-2102: 2 (Folder)
Requirements Folder
- IE Object Type: Function

### Chapter-2103: 2.1 (Folder)
Requirements Subfolder
N/A
- IE Object Type: Function

#### Requirement-555556: 2.1.1 (Requirement)
Another Requirement
Requirement must be Requirement
- IE Object Type: Requirement

#### Requirement-555557: 2.1.2 (Requirement)
Requirement with Image
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/Figure 1 Sample Image (part)
- IE Object Type: Requirement
